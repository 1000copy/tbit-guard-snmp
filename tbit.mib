--- reco 2nd mib 
tbitinc DEFINITIONS ::= BEGIN
    IMPORTS  enterprises,OBJECT-TYPE,NOTIFICATION-TYPE FROM SNMPv2-SMI;
    tbit OBJECT IDENTIFIER ::= { enterprises 66666 }
    RecoSecret OBJECT-TYPE
        SYNTAX INTEGER
        MAX-ACCESS read-write
        STATUS current
        DESCRIPTION
            "Description."
        ::= { tbit 1 }
	RecoSecretTrap NOTIFICATION-TYPE
		OBJECTS { Name }
		STATUS current
		DESCRIPTION 
			"Description."
		::= { tbit 2 }
END
