NET-SNMP-EXAMPLES-MIB DEFINITIONS ::= BEGIN
IMPORTS
    enterprises,MODULE-IDENTITY, OBJECT-TYPE, Integer32 FROM SNMPv2-SMI;
netSnmpExamples MODULE-IDENTITY
    LAST-UPDATED ""
    ORGANIZATION ""
    CONTACT-INFO ""
    DESCRIPTION ""
    REVISION     ""    
    ::= { enterprises 2 }
netSnmpExampleTables        OBJECT IDENTIFIER ::= { netSnmpExamples 2 }
netSnmpIETFWGTable OBJECT-TYPE
    SYNTAX      SEQUENCE OF NetSnmpIETFWGEntry
    MAX-ACCESS  not-accessible
    STATUS      current
    DESCRIPTION
	""
    ::= { netSnmpExampleTables 1 }

netSnmpIETFWGEntry OBJECT-TYPE
    SYNTAX      NetSnmpIETFWGEntry
    MAX-ACCESS  not-accessible
    STATUS      current
    DESCRIPTION
	"A row describing a given working group"
    INDEX   { nsIETFWGName }
    ::= {netSnmpIETFWGTable 1 }
NetSnmpIETFWGEntry ::= SEQUENCE {
	nsIETFWGName	OCTET STRING
}
nsIETFWGName OBJECT-TYPE
    SYNTAX      OCTET STRING (SIZE(1..32))
    MAX-ACCESS  not-accessible
    STATUS      current
    DESCRIPTION
	"The name of the IETF Working Group this table describes."
    ::= { netSnmpIETFWGEntry 1 }
placeholder OBJECT IDENTIFIER ::= { netSnmpExamples 3 }
END
