--- reco 3rd mib 
--- 1.3.6.1.4.1.66666.1
TBITINC DEFINITIONS ::= BEGIN
    IMPORTS  MODULE-IDENTITY,enterprises,OBJECT-TYPE,NOTIFICATION-TYPE FROM SNMPv2-SMI;
    TBITINC MODULE-IDENTITY
    LAST-UPDATED "200006140000Z"
    ORGANIZATION "IETF Interfaces MIB Working Group"
    CONTACT-INFO
            "   Keith McCloghrie
                Cisco Systems, Inc.
                170 West Tasman Drive
                San Jose, CA  95134-1706
                US

                408-526-5260
                kzm@cisco.com"
    DESCRIPTION
            "The MIB module to describe generic objects for network
            interface sub-layers.  This MIB is an updated version of
            MIB-II's ifTable, and incorporates the extensions defined in
            RFC 1229."

    REVISION      "200006140000Z"
    DESCRIPTION
            "Clarifications agreed upon by the Interfaces MIB WG, and
            published as RFC 2863."
    REVISION      "199602282155Z"
    DESCRIPTION
            "Revisions made by the Interfaces MIB WG, and published in
            RFC 2233."
    REVISION      "199311082155Z"
    DESCRIPTION
            "Initial revision, published as part of RFC 1573."
    ::= { mib-2 31 }
    tbit OBJECT IDENTIFIER ::= { enterprises 66666 }
    ifTable OBJECT-TYPE
    SYNTAX      SEQUENCE OF IfEntry
    MAX-ACCESS  not-accessible
    STATUS      current
    DESCRIPTION
            "A list of interface entries.  The number of entries is
            given by the value of ifNumber."
    ::= { tbit 2 }

    ifEntry OBJECT-TYPE
        SYNTAX      IfEntry
        MAX-ACCESS  not-accessible
        STATUS      current
        DESCRIPTION
                "An entry containing management information applicable to a
                particular interface."
        INDEX   { ifIndex }
        ::= { ifTable 1 }

    IfEntry ::=
        SEQUENCE {
            ifIndex                 INTEGER,
            ifType                  INTEGER            
        }

    ifIndex OBJECT-TYPE
        SYNTAX      INTEGER
        MAX-ACCESS  read-only
        STATUS      current
        DESCRIPTION
                "A unique value, greater than zero, for each interface.  It
                is recommended that values are assigned contiguously
                starting from 1.  The value for each interface sub-layer
                must remain constant at least from one re-initialization of
                the entity's network management system to the next re-
                initialization."
        ::= { ifEntry 1 }


    ifType OBJECT-TYPE
        SYNTAX      INTEGER
        MAX-ACCESS  read-only
        STATUS      current
        DESCRIPTION
                "The type of interface.  Additional values for ifType are
                assigned by the Internet Assigned Numbers Authority (IANA),
                through updating the syntax of the IANAifType textual
                convention."
        ::= { ifEntry 2 }

END
