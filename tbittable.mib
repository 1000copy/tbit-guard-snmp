--- reco 3rd mib 
--- 1.3.6.1.4.1.66666.1
tbitinc DEFINITIONS ::= BEGIN
    IMPORTS  enterprises,OBJECT-TYPE,NOTIFICATION-TYPE FROM SNMPv2-SMI;
    tbit OBJECT IDENTIFIER ::= { enterprises 66666 }
    ifTable OBJECT-TYPE
    SYNTAX      SEQUENCE OF IfEntry
    MAX-ACCESS  not-accessible
    STATUS      current
    DESCRIPTION
            "A list of interface entries.  The number of entries is
            given by the value of ifNumber."
    ::= { tbit 2 }

    ifEntry OBJECT-TYPE
        SYNTAX      IfEntry
        MAX-ACCESS  not-accessible
        STATUS      current
        DESCRIPTION
                "An entry containing management information applicable to a
                particular interface."
        INDEX   { ifIndex }
        ::= { ifTable 1 }

    IfEntry ::=
        SEQUENCE {
            ifIndex                 InterfaceIndex,
            ifDescr                 DisplayString,
            ifType                  IANAifType            
        }

    ifIndex OBJECT-TYPE
        SYNTAX      InterfaceIndex
        MAX-ACCESS  read-only
        STATUS      current
        DESCRIPTION
                "A unique value, greater than zero, for each interface.  It
                is recommended that values are assigned contiguously
                starting from 1.  The value for each interface sub-layer
                must remain constant at least from one re-initialization of
                the entity's network management system to the next re-
                initialization."
        ::= { ifEntry 1 }

    ifDescr OBJECT-TYPE
        SYNTAX      DisplayString (SIZE (0..255))
        MAX-ACCESS  read-only
        STATUS      current
        DESCRIPTION
                "A textual string containing information about the
                interface.  This string should include the name of the
                manufacturer, the product name and the version of the
                interface hardware/software."
        ::= { ifEntry 2 }

    ifType OBJECT-TYPE
        SYNTAX      IANAifType
        MAX-ACCESS  read-only
        STATUS      current
        DESCRIPTION
                "The type of interface.  Additional values for ifType are
                assigned by the Internet Assigned Numbers Authority (IANA),
                through updating the syntax of the IANAifType textual
                convention."
        ::= { ifEntry 3 }

END
